Dim storePath

' Sub to read the Store Path
Function ReadSPath()
  os = UCase(Left(CATIA.SystemConfiguration.OperatingSystem, 3))
  sep = "/"
  If (os = "WIN") Or (os = "INT") Then
    sep = "\"
  End If

  If (Len(storePath) = 0) Then
    ret = InputBox("Enter Path for CATPart or CATProduct (e.g. c:" + sep + "catfiles" + sep + ")", "Save as")
    storePath = ret
  End If

  Set fso = CreateObject("Scripting.FileSystemObject")

  If (Len(storePath) = 0) Or (fso.FolderExists(storePath) = False) Then
    Set fso = Nothing
    ReadSPath = Empty
    Exit Function
  End If

  If (Mid(storePath, Len(storePath), 1) <> sep) Then
    storePath = storePath + sep
  End If

  ReadSPath = storePath
  Set fso = Nothing
End Function

' Sub to store a document'
Sub SaveDocument(document, name)
  document.SaveAs storePath & name
End Sub

' Sub to retrieve a name in capital letters'
Function GetUCaseName(name)
  ucaseName = Left(name, InStrRev(name, ".") - 1)
  extension = Right(name, Len(name) - InStr(name, ".") + 1)
  GetUCaseName = UCase(ucaseName) + extension
End Function

Function GetBrep(SelectionToBRepDisplayName As String) As String
  MyBRepName = Replace(SelectionToBRepDisplayName, "Selection_", "")
  MyBRepName = Left(MyBRepName, InStrRev(MyBRepName, "));"))
  MyBRepName = MyBRepName + ");WithTemporaryBody;WithoutBuildError;WithDefaultFeatureSupport;MonoFond;MFBRepVersion_CXR15)"
  GetBrep = MyBRepName
End Function

Function GetFaceEdgeSelections(document, faceSelection)
  searchStr = faceSelection.Reference.DisplayName
  searchStr = Mid(searchStr, InStr(searchStr, "Brp:"))
  searchStr = Left(searchStr, InStr(searchStr, "Cf11:()") + 6)
  Set selection = document.Selection
  selection.Clear
  selection.Search "Topology.CGMEdge, all"
  Dim edgeArr(1000)
  i = 1
  For j = 1 To selection.Count
    Set selEdge = selection.Item2(j)
    edgeRef = selEdge.Reference.DisplayName
    If (InStr(edgeRef, searchStr)) Then
      Set edgeArr(i) = selEdge
      i = i + 1
    End If
  Next
  edgeArr(0) = i - 1
  GetFaceEdgeSelections = edgeArr
  selection.Clear
End Function

Function GetFaceFaceEdgeSelections(document, faceSelection1, faceSelection2)
  searchStr1 = faceSelection1.Reference.DisplayName
  searchStr1 = Mid(searchStr1, InStr(searchStr1, "Brp:"))
  searchStr1 = Left(searchStr1, InStr(searchStr1, "Cf11:()") + 6)
  searchStr2 = faceSelection2.Reference.DisplayName
  searchStr2 = Mid(searchStr2, InStr(searchStr2, "Brp:"))
  searchStr2 = Left(searchStr2, InStr(searchStr2, "Cf11:()") + 6)
  Set selection = document.Selection
  selection.Clear
  selection.Search "Topology.CGMEdge, all"
  Dim edgeArr(1000)
  i = 1
  For j = 1 To selection.Count
    Set selEdge = selection.Item2(j)
    edgeRef = selEdge.Reference.DisplayName
    If (InStr(edgeRef, searchStr1) And InStr(edgeRef, searchStr2)) Then
      Set edgeArr(i) = selEdge
      i = i + 1
    End If
  Next
  edgeArr(0) = i - 1
  GetFaceFaceEdgeSelections = edgeArr
  selection.Clear
End Function

  Function GetFaceReferenceByPoint(document, wpart, x, y, z,nx,ny,nz,eps)
    Set shapeFactory1 = wpart.ShapeFactory
    Set hybridShapeFactory1 = wpart.HybridShapeFactory
    Set Body = wpart.MainBody
    Set Point = hybridShapeFactory1.AddNewPointCoord(x, y, z)
     Set HybridBody1 = wPart.hybridBodies.item(1)
     HybridBody1.AppendHybridShape Point
  wPart.InWorkObject = Point
  wPart.Update

    Set Selection = document.Selection
    Selection.Clear
    Selection.Search ("Topology.CGMFace, all")
    Set pointReference = wpart.CreateReferenceFromObject(Point)
    Set SPAWorkbench = document.GetWorkbench("SPAWorkbench")
    Set pointmeasure = SPAWorkbench.GetMeasurable(Point)
    mindistance = eps
    Set targetface1 = Nothing
    Set targetReferenceface1 = Nothing
    Set faceSelection = Nothing
    Set facereference = Nothing
    Set Face = Nothing
    Dim varCATSafeArrayVariant(3) As Variant
    Dim dir1(3) As Variant
    Dim dir2(3) As Variant
    Dim i
    For i = 1 To Selection.Count
      Set faceSelection = Selection.Item(i)
      Set facereference = faceSelection.Reference
      Set Face = faceSelection.Value
      validface = False
      If faceSelection.Type = "PlanarFace" Then
        Face.GetFirstAxis (dir1)
        Face.GetSecondAxis (dir2)
        varCATSafeArrayVariant(0) = dir1(1) * dir2(2) - dir1(2) * dir2(1)
        varCATSafeArrayVariant(1) = dir1(2) * dir2(0) - dir1(0) * dir2(2)
        varCATSafeArrayVariant(2) = dir1(0) * dir2(1) - dir1(1) * dir2(0)
        validFace = True
      ElseIf faceSelection.Type = "CylindricalFace" Then
        Face.GetDirection (varCATSafeArrayVariant)
        validface = True
      End If
      If validface Then
        sk = Abs(varCATSafeArrayVariant(0) * nx + varCATSafeArrayVariant(1) * ny + varCATSafeArrayVariant(2) * nz)
        If sk > 1 - 0.00001 Then
          Distance = pointmeasure.GetMinimumDistance(facereference)
          If Distance < mindistance Then
            Set targetface1 = faceSelection
            Set targetReferenceface1 = facereference
            mindistance = Distance
          End If
        End If
      End If
    Next
    Selection.Clear
    Selection.Add (Point)
    Selection.Delete
    Set GetFaceReferenceByPoint = targetReferenceface1
  End Function
Function toolCall0(wpart,HybridBody1)
  set backWork = wPart.InWorkObject 
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  wPart.InWorkObject=backWork
  Set toolCall0=absref
End Function

Function toolCall1(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(0, 3)
  Set endPoint = Factory2D.CreatePoint(6, 3)
  Set line = factory2d.CreateLine(0, 3, 6, 3)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(6, 3)
  Set endPoint = Factory2D.CreatePoint(6, 4)
  Set line = factory2d.CreateLine(6, 3, 6, 4)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(6, 4)
  Set endPoint = Factory2D.CreatePoint(5.025, 4.5715834237166)
  Set cir = Factory2D.CreateCircle(3, 7.105427357601e-14, 4.9999999999999, 0.92729521800161, 1.1538174961752)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(5.025, 4.5715834237166)
  Set endPoint = Factory2D.CreatePoint(5.025, 6)
  Set line = factory2d.CreateLine(5.025, 4.5715834237166, 5.025, 6)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(5.025, 6)
  Set endPoint = Factory2D.CreatePoint(5.25, 6)
  Set line = factory2d.CreateLine(5.025, 6, 5.25, 6)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(5.25, 6)
  Set endPoint = Factory2D.CreatePoint(5.25, 12.803808027302)
  Set line = factory2d.CreateLine(5.25, 6, 5.25, 12.803808027302)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(5.25, 12.803808027302)
  Set endPoint = Factory2D.CreatePoint(0.75, 12.803808027302)
  Set cir = Factory2D.CreateCircle(3, 2.6645352591004e-14, 13, 1.3968434390788, 1.744749214511)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0.75, 12.803808027302)
  Set endPoint = Factory2D.CreatePoint(0.75, 6)
  Set line = factory2d.CreateLine(0.75, 12.803808027302, 0.75, 6)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0.75, 6)
  Set endPoint = Factory2D.CreatePoint(0.97499999999999, 6)
  Set line = factory2d.CreateLine(0.75, 6, 0.97499999999999, 6)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0.97499999999999, 6)
  Set endPoint = Factory2D.CreatePoint(0.97499999999999, 4.5715834237166)
  Set line = factory2d.CreateLine(0.97499999999999, 6, 0.97499999999999, 4.5715834237166)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0.97499999999999, 4.5715834237166)
  Set endPoint = Factory2D.CreatePoint(0, 4)
  Set cir = Factory2D.CreateCircle(3.0000000000001, -1.6875389974302e-13, 5.0000000000002, 1.9877751574146, 2.2142974355882)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0, 4)
  Set endPoint = Factory2D.CreatePoint(0, 3)
  Set line = factory2d.CreateLine(0, 4, 0, 3)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set pk1 = Factory2D.CreatePoint(100, 0)
  Set pk2 = Factory2D.CreatePoint(-100, 0)
  Set line = Factory2d.CreateLine(100, 0, -100, 0)
  sketch.CenterLine = line
  Set ref1 = wpart.CreateReferenceFromObject(pk1)
  Set ref2 = wpart.CreateReferenceFromObject(pk2)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  wPart.Update

  Sketch.CloseEdition
  Set sketch3 = sketch
  wPart.Update
  Set toolCall1=sketch3
End Function

Function toolCall2(wpart,HybridBody1)
  set backWork = wPart.InWorkObject 
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 0, -1)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  wPart.InWorkObject=backWork
  Set toolCall2=absref
End Function

Function toolCall3(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(-19, -22)
  Set endPoint = Factory2D.CreatePoint(25, -22)
  Set line = factory2d.CreateLine(-19, -22, 25, -22)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(25, -22)
  Set endPoint = Factory2D.CreatePoint(25, 22)
  Set line = factory2d.CreateLine(25, -22, 25, 22)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(25, 22)
  Set endPoint = Factory2D.CreatePoint(-19, 22)
  Set line = factory2d.CreateLine(25, 22, -19, 22)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-19, 22)
  Set endPoint = Factory2D.CreatePoint(-19, -22)
  Set line = factory2d.CreateLine(-19, 22, -19, -22)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set pk = Factory2D.CreatePoint(3, 0)
  Set cir = Factory2D.CreateClosedCircle(3, 0, 11)
  Set ref1 = wpart.CreateReferenceFromObject(pk)
  Set ref2 = wpart.CreateReferenceFromObject(cir)
  Set constraint1 = constraints1.AddMonoEltCst(catCstTypeReference, ref1)
  Set constraint1 = constraints1.AddMonoEltCst(catCstTypeReference, ref2)

  wPart.Update

  Sketch.CloseEdition
  Set sketch5 = sketch
  wPart.Update
  Set toolCall3=sketch5
End Function

Function toolCall4(wpart,HybridBody1)
  set backWork = wPart.InWorkObject 
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  wPart.InWorkObject=backWork
  Set toolCall4=absref
End Function

Function toolCall5(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(3, -6.5)
  Set endPoint = Factory2D.CreatePoint(6, -6.5)
  Set line = factory2d.CreateLine(3, -6.5, 6, -6.5)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(6, -6.5)
  Set endPoint = Factory2D.CreatePoint(6, -20)
  Set line = factory2d.CreateLine(6, -6.5, 6, -20)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(6, -20)
  Set endPoint = Factory2D.CreatePoint(3, -20)
  Set line = factory2d.CreateLine(6, -20, 3, -20)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(3, -20)
  Set endPoint = Factory2D.CreatePoint(3, -6.5)
  Set line = factory2d.CreateLine(3, -20, 3, -6.5)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set pk1 = Factory2D.CreatePoint(3, -20)
  Set pk2 = Factory2D.CreatePoint(3, -6.5)
  Set line = Factory2d.CreateLine(3, -20, 3, -6.5)
  sketch.CenterLine = line
  Set ref1 = wpart.CreateReferenceFromObject(pk1)
  Set ref2 = wpart.CreateReferenceFromObject(pk2)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  wPart.Update

  Sketch.CloseEdition
  Set sketch7 = sketch
  wPart.Update
  Set toolCall5=sketch7
End Function

Function toolCall6(wpart,HybridBody1)
  set backWork = wPart.InWorkObject 
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  wPart.InWorkObject=backWork
  Set toolCall6=absref
End Function

Function toolCall7(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(3, -20)
  Set endPoint = Factory2D.CreatePoint(5.3865, -20)
  Set line = factory2d.CreateLine(3, -20, 5.3865, -20)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(5.3865, -20)
  Set endPoint = Factory2D.CreatePoint(6, -20.6135)
  Set line = factory2d.CreateLine(5.3865, -20, 6, -20.6135)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(6, -20.6135)
  Set endPoint = Factory2D.CreatePoint(6, -35.3865)
  Set line = factory2d.CreateLine(6, -20.6135, 6, -35.3865)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(6, -35.3865)
  Set endPoint = Factory2D.CreatePoint(5.3865, -36)
  Set line = factory2d.CreateLine(6, -35.3865, 5.3865, -36)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(5.3865, -36)
  Set endPoint = Factory2D.CreatePoint(3, -36)
  Set line = factory2d.CreateLine(5.3865, -36, 3, -36)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(3, -36)
  Set endPoint = Factory2D.CreatePoint(3, -20)
  Set line = factory2d.CreateLine(3, -36, 3, -20)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set pk1 = Factory2D.CreatePoint(3, -36)
  Set pk2 = Factory2D.CreatePoint(3, -20)
  Set line = Factory2d.CreateLine(3, -36, 3, -20)
  sketch.CenterLine = line
  Set ref1 = wpart.CreateReferenceFromObject(pk1)
  Set ref2 = wpart.CreateReferenceFromObject(pk2)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  wPart.Update

  Sketch.CloseEdition
  Set sketch9 = sketch
  wPart.Update
  Set toolCall7=sketch9
End Function

Function toolCall9(wpart,HybridBody1)
  set backWork = wPart.InWorkObject 
  wPart.InWorkObject = HybridBody1
  wPart.Update

  Set hypFact = wPart.HybridShapeFactory
  Set HybridShapePointCoord0 = hypFact.AddNewPointCoord(3, -36, 0)
  HybridBody1.AppendHybridShape HybridShapePointCoord0
  wPart.InWorkObject = HybridShapePointCoord0
  wPart.Update

  Set HybridShapePointCoord1 = hypFact.AddNewPointCoord(4, -36, 0)
  HybridBody1.AppendHybridShape HybridShapePointCoord1
  wPart.InWorkObject = HybridShapePointCoord1
  wPart.Update

  Set HybridShapePointCoord2 = hypFact.AddNewPointCoord(3, -36, -1)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  wPart.InWorkObject=backWork
  Set toolCall9=absref
End Function

Function toolCall8(partdocument,wpart,body)
  set thread=nothing
  set cylCatiaFace=GetFaceReferenceByPoint(partdocument,wpart,3,-28,-3,0,1,0,0.01)
  if not cylCatiaFace is nothing then
     Set HybridBody1 = wPart.hybridBodies.item(1)
  Set absref=toolCall9(wpart,HybridBody1)
     set plaCatiaFace=absref
    if not cylCatiaFace is nothing then
      wPart.InWorkObject = Body
      Set thread = wpart.ShapeFactory.AddNewThreadWithOutRef()
      thread.Diameter = 6
      thread.Pitch = 1
      thread.Depth = 14.773
      thread.LateralFaceElement = cylCatiaFace
      thread.LimitFaceElement = plaCatiaFace
      thread.name = "M6"
      on error resume next
      wpart.Update
      if err.number<> 0 then 
        wpart.Inactivate thread
      end if
      on error goto 0
    end if
  end if
  Set toolCall8=thread
End Function

Function toolCall10(wpart,HybridBody1)
  set backWork = wPart.InWorkObject 
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  wPart.InWorkObject=backWork
  Set toolCall10=absref
End Function

Function toolCall11(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(5.25, -10)
  Set endPoint = Factory2D.CreatePoint(11.25, -16)
  Set line = factory2d.CreateLine(5.25, -10, 11.25, -16)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(11.25, -16)
  Set endPoint = Factory2D.CreatePoint(11.25, -6.5)
  Set line = factory2d.CreateLine(11.25, -16, 11.25, -6.5)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(11.25, -6.5)
  Set endPoint = Factory2D.CreatePoint(5.25, -6.5)
  Set line = factory2d.CreateLine(11.25, -6.5, 5.25, -6.5)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(5.25, -6.5)
  Set endPoint = Factory2D.CreatePoint(5.25, -10)
  Set line = factory2d.CreateLine(5.25, -6.5, 5.25, -10)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  wPart.Update

  Sketch.CloseEdition
  Set sketch11 = sketch
  wPart.Update
  Set toolCall11=sketch11
End Function

Function toolCall12(wpart,HybridBody1)
  set backWork = wPart.InWorkObject 
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  wPart.InWorkObject=backWork
  Set toolCall12=absref
End Function

Function toolCall13(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(-5.25, -16)
  Set endPoint = Factory2D.CreatePoint(0.75, -10)
  Set line = factory2d.CreateLine(-5.25, -16, 0.75, -10)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0.75, -10)
  Set endPoint = Factory2D.CreatePoint(0.75, -6.5)
  Set line = factory2d.CreateLine(0.75, -10, 0.75, -6.5)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0.75, -6.5)
  Set endPoint = Factory2D.CreatePoint(-5.25, -6.5)
  Set line = factory2d.CreateLine(0.75, -6.5, -5.25, -6.5)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-5.25, -6.5)
  Set endPoint = Factory2D.CreatePoint(-5.25, -16)
  Set line = factory2d.CreateLine(-5.25, -6.5, -5.25, -16)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  wPart.Update

  Sketch.CloseEdition
  Set sketch13 = sketch
  wPart.Update
  Set toolCall13=sketch13
End Function

Sub CreatePart1
  On Error Resume Next

  Set SaveCaseDoc = CATIA.Documents.Item("SA_6_E.CATPart")

  If (Err.Number <> 0) Then
    ucaseName = GetUCaseName("SA_6_E.CATPart")
    Set SaveCaseDoc = CATIA.Documents.Item(ucaseName)
  End If

  Set PartDocument = SaveCaseDoc

  If (IsObject(PartDocument)) Then
    wPart.Activate
    Exit Sub
  End If

  Set fso = CreateObject("Scripting.FileSystemObject")

  If (fso.FileExists(storePath & "SA_6_E.CATPart")) Then
    CATIA.Documents.Open(storePath & "SA_6_E.CATPart")
    Set fso = Nothing
    Exit Sub
  ElseIf (fso.FileExists(storePath & GetUCaseName("SA_6_E.CATPart"))) Then
    CATIA.Documents.Open(storePath & GetUCaseName("SA_6_E.CATPart"))
    Set fso = Nothing
    Exit Sub
  End If

  Set fso = Nothing

  On Error Goto 0

  Set PartDocument = CATIA.Documents.Add("Part")
  Set unused1 = Partdocument.GetItem(1).UserRefProperties.CreateString("NN", "AHR_003")
  Set unused1 = Partdocument.GetItem(1).UserRefProperties.CreateString("NT", "Rod ends with a male thread")
  Set unused1 = Partdocument.GetItem(1).UserRefProperties.CreateString("NB", "SA 6 E")
  Set unused1 = Partdocument.GetItem(1).UserRefProperties.CreateString("NBSYN", "$DESIGNATION.")
  Set unused1 = Partdocument.GetItem(1).UserRefProperties.CreateString("LINA", "SA 6 E")
  Set unused1 = Partdocument.GetItem(1).UserRefProperties.CreateString("DESIGNATION", "SA 6 E")
  Set unused1 = Partdocument.GetItem(1).UserRefProperties.CreateString("DD", "6.000")
  Set unused1 = Partdocument.GetItem(1).UserRefProperties.CreateString("B", "6.000")
  Set unused1 = Partdocument.GetItem(1).UserRefProperties.CreateString("G", "M 6")
  Set unused1 = Partdocument.GetItem(1).UserRefProperties.CreateString("C1", "4.500")
  Set unused1 = Partdocument.GetItem(1).UserRefProperties.CreateString("DD2", "22.000")
  Set unused1 = Partdocument.GetItem(1).UserRefProperties.CreateString("HH", "36.000")
  Set unused1 = Partdocument.GetItem(1).UserRefProperties.CreateString("AT", "13.000")
  Set unused1 = Partdocument.GetItem(1).UserRefProperties.CreateString("LOAD1", "3.400")
  Set unused1 = Partdocument.GetItem(1).UserRefProperties.CreateString("LOAD2", "8.150")
  Set unused1 = Partdocument.GetItem(1).UserRefProperties.CreateString("VENDOR", "SKF")
  Set unused1 = Partdocument.GetItem(1).UserRefProperties.CreateString("SUPPLIER", "SKF")
  Set unused1 = Partdocument.GetItem(1).UserRefProperties.CreateString("ARTICLENO", "SA 6 E")
  Set unused1 = Partdocument.GetItem(1).UserRefProperties.CreateString("BOMINFO", "SA 6 E")
  Set unused1 = Partdocument.GetItem(1).UserRefProperties.CreateString("CREATOR", "CADENAS GmbH")
  Partdocument.GetItem(1).PartNumber = "SA 6 E-SA 6 E"
  Partdocument.GetItem(1).Definition = "Cadenas PARTsolutions"
  Partdocument.GetItem(1).DescriptionRef = "Rod ends with a male thread"
  Set mident = Partdocument.GetItem(1).UserRefProperties.CreateString("mident", "{$CADENAS_DATA\23d-libs\skf\bearings_units_and_housings\plain_bearings\rod_ends\ahr_003.prj},156 {VTYP=3D},{NB=SA 6 E},{LINA=SA 6 E},{NN=AHR_003},{DATE=12.09.2016 08:57:12},{GEOMDATE=13.05.2016 10:23:42},{VERSION=},{LINEID=17870},{WBVAR=},{WBNUMERIC=}  {NB=SA 6 E},{LINA=SA 6 E},{KT=DUMMY},{PRODUCTID=208020000},{DESIGNATION=SA 6 E},{DD=6.000},{B=6.000},{DDK=10.000},{G=M 6},{C1=4.500},{DD2=22.000},{HH=36.000},{LL1=16.000},{LL2=49.000},{LL7=10.000},{R1=0.300},{AT=13.000},{LOAD1=3.400},{LOAD2=8.150},{MASS=0.017},{TYPEID=208020},{TAXONOMY=1},{BZ=6},{GALG=0.5},{TP=1},{DESIGN=rodend_male1},{MAPPING=BAZ50,DESIGNATION|IRD01,DD|IRL01,B|IRD20,DDK|HOT01,G|HOL01A,C1|HOD01A,DD2|HOL35,HH|HOL50B,LL1|HOL40A,LL2|HOL10B,LL7|IRR20,R1|BCA10,AT|BCC02,LOAD1|HOC16,LOAD2|BAM01,MASS},{DESIGNLIST=rodend_male1,rodend_male1x},{SORT=DD},{PIM=SA 6 E}")

  set wpart=partDocument.Part
  Dim skCoord(8)
  Dim Body
  Set Body = wPart.MainBody
  Body.Name="SA 6 E"

  Dim HybridBody1
  Set HybridBody1 = wPart.HybridBodies.Add
  HybridBody1.Name="SA 6 E Geo"

  Set absref=toolCall0(wpart,HybridBody1)
  Set sketch3=toolCall1(wpart,body,absref)
  wPart.InWorkObject = Body
  wPart.Update

  Set shaft = wPart.ShapeFactory.AddNewShaft(sketch3)
  shaft.firstAngle.value = 0
  shaft.SecondAngle.value = 360
  wPart.Update

  Set absref=toolCall2(wpart,HybridBody1)
  Set sketch5=toolCall3(wpart,body,absref)
  wPart.InWorkObject = Body
  wPart.Update

  Set pocket = wPart.ShapeFactory.AddNewPocket(sketch5, 22)
  pocket.IsSymmetric = True
  wPart.Update

  Set absref=toolCall4(wpart,HybridBody1)
  Set sketch7=toolCall5(wpart,body,absref)
  wPart.InWorkObject = Body
  wPart.Update

  Set shaft = wPart.ShapeFactory.AddNewShaft(sketch7)
  shaft.firstAngle.value = 0
  shaft.SecondAngle.value = 360
  wPart.Update

  Set absref=toolCall6(wpart,HybridBody1)
  Set sketch9=toolCall7(wpart,body,absref)
  wPart.InWorkObject = Body
  wPart.Update

  Set shaft = wPart.ShapeFactory.AddNewShaft(sketch9)
  shaft.firstAngle.value = 0
  shaft.SecondAngle.value = 360
  wPart.Update

  Set thread10=toolCall8(partdocument,wpart,body)
  Set absref=toolCall10(wpart,HybridBody1)
  Set sketch11=toolCall11(wpart,body,absref)
  wPart.InWorkObject = Body
  wPart.Update

  Set pocket = wPart.ShapeFactory.AddNewPocket(sketch11, 22)
  pocket.IsSymmetric = True
  wPart.Update

  Set absref=toolCall12(wpart,HybridBody1)
  Set sketch13=toolCall13(wpart,body,absref)
  wPart.InWorkObject = Body
  wPart.Update

  Set pocket = wPart.ShapeFactory.AddNewPocket(sketch13, 22)
  pocket.IsSymmetric = True
  wPart.Update

  Partdocument.Selection.Clear
  Partdocument.Selection.Add HybridBody1
  Partdocument.Selection.VisProperties.SetShow 1
  Partdocument.Selection.Clear
  SaveDocument PartDocument, "SA_6_E.CATPart"
End Sub

Sub CreatePSolMain
  On Error Resume Next

  Set PartDocument = CATIA.Documents.Item("SA_6_E.CATPart")

  If (IsObject(PartDocument)) Then
    wPart.Activate
    Exit Sub
  End If

  If (IsEmpty(readSPath)) Then
    Exit Sub
  End If

  Set fso = CreateObject("Scripting.FileSystemObject")

  If (fso.FileExists(storePath & "SA_6_E.CATPart")) Then
    CATIA.Documents.Open(storePath & "SA_6_E.CATPart")
    Set fso = Nothing
    Exit Sub
  End If

  Set fso = Nothing

  On Error Goto 0

  CreatePart1


End Sub

CreatePSolMain
